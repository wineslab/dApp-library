-- Simple Service Model ASN.1 Definitions
-- This service model extends E3 messages for the example application
--
-- Usage with E3 Protocol:
-- - Simple-IndicationData   is encoded into E3-IndicationMessage.protocolData
-- - Simple-DAppControlData  is encoded into E3-DAppControlAction.actionData
-- - Simple-DAppReportData   is encoded into E3-DAppReport.reportData
-- - Simple-XAppControlData  is encoded into E3-XAppControlAction.xAppControlData
--
-- Each "*Data" envelope is a (Type, Payload) pair: the Type enum is a human-
-- readable discriminator and the Payload CHOICE carries the variant body.

SIMPLE-SM DEFINITIONS AUTOMATIC TAGS ::= BEGIN

-- ============================================================================
-- RAN FUNCTION DATA MESSAGE STRUCTURES
-- ============================================================================

Simple-RanFunctionData ::= SEQUENCE {
    name                   UTF8String (SIZE (0..100))  -- Name of the SM
}

-- ============================================================================
-- INDICATION MESSAGE STRUCTURES
-- ============================================================================

-- Simple Indication (random data from RAN)
Simple-Indication ::= SEQUENCE {
    data1                   INTEGER (0..32768),              -- Random data
    timestamp               INTEGER (0..2147483647) OPTIONAL -- Unix timestamp when samples were captured
}

Simple-IndicationType ::= ENUMERATED {
    simple                  (0)
}

Simple-IndicationPayload ::= CHOICE {
    simpleIndication        Simple-Indication
}

Simple-IndicationData ::= SEQUENCE {
    indicationType          Simple-IndicationType,
    indicationPayload       Simple-IndicationPayload
}

-- ============================================================================
-- dAPP CONTROL ACTION STRUCTURES
-- ============================================================================

-- Simple Control (main control message used by dApp)
Simple-Control ::= SEQUENCE {
    samplingThreshold       INTEGER (0..100) OPTIONAL        -- Sampling delivery ratio
}

Simple-DAppControlType ::= ENUMERATED {
    simple                  (0)
}

Simple-DAppControlPayload ::= CHOICE {
    simpleControl           Simple-Control
}

Simple-DAppControlData ::= SEQUENCE {
    controlType             Simple-DAppControlType,
    controlPayload          Simple-DAppControlPayload
}

-- ============================================================================
-- dAPP REPORT STRUCTURES
-- ============================================================================

Simple-DAppReport ::= SEQUENCE {
    bin1                INTEGER (0..100)
}

Simple-DAppReportType ::= ENUMERATED {
    simple                  (0)
}

Simple-DAppReportPayload ::= CHOICE {
    simpleReport            Simple-DAppReport
}

Simple-DAppReportData ::= SEQUENCE {
    reportType              Simple-DAppReportType,
    reportPayload           Simple-DAppReportPayload
}

-- ============================================================================
-- xAPP CONTROL ACTION STRUCTURES
-- ============================================================================

-- Simple Configuration Control
Simple-ConfigControl ::= SEQUENCE {
    enable                  BOOLEAN                -- Enable/disable data delivery
}

Simple-XAppControlType ::= ENUMERATED {
    config                  (0)
}

Simple-XAppControlPayload ::= CHOICE {
    configControl           Simple-ConfigControl
}

Simple-XAppControlData ::= SEQUENCE {
    controlType             Simple-XAppControlType,
    controlPayload          Simple-XAppControlPayload
}

END
